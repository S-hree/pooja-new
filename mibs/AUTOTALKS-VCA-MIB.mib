AUTOTALKS-VCA-MIB DEFINITIONS ::= BEGIN

IMPORTS
    MODULE-IDENTITY, OBJECT-TYPE, Unsigned32
        FROM SNMPv2-SMI
    MODULE-COMPLIANCE, OBJECT-GROUP
        FROM SNMPv2-CONF
    TruthValue
        FROM SNMPv2-TC
    ifIndex
        FROM IF-MIB
    atlkMgmt
        FROM AUTOTALKS-REG
    ConfigSaveStatus
        FROM AUTOTALKS-TC
;

vcaMib MODULE-IDENTITY
    LAST-UPDATED "201507160000Z"
    ORGANIZATION "Autotalks"
    CONTACT-INFO "Grand Netter Building
                  POB 3846, Kfar-Netter 40593, Israel
                  Phone: (+972)-9-886-5300
                  Fax:   (+972)-9-886-5301
                  info@auto-talks.com"
    DESCRIPTION  "VCA (V2X Communication Analyzer) MIB."
    REVISION     "201507160000Z"
    DESCRIPTION  "Added vcaConfigSaveStatus attribute."
    REVISION     "201403130000Z"
    DESCRIPTION  "Changed value range of attribute vcaFrameLen."
    REVISION     "201311190000Z"
    DESCRIPTION  "Added vcaRx identifier and vcaBsmRxEnabled attribute."
    REVISION     "201212200000Z"
    DESCRIPTION  "Initial revision."
    ::= { atlkMgmt 5 }

--
-- VCA RX
--

vcaRx OBJECT IDENTIFIER ::= { vcaMib 2 }

vcaBsmRxEnabled OBJECT-TYPE
    SYNTAX        TruthValue
    MAX-ACCESS    read-write
    STATUS        current
    DESCRIPTION
        "Whether BSM reception is enabled."
    ::= { vcaRx 1 }

--
-- VCA log mode scalar
--

vcaLogMode OBJECT-TYPE
    SYNTAX        INTEGER { off(0), ifHasNavFix(1), ifHasTrueTime(2) }
    MAX-ACCESS    read-write
    STATUS        current
    DESCRIPTION
        "VCA logging modes:

         off -- No logging.
         ifHasNavFix -- Log only when navigation fix is available.
         ifHasTrueTime -- Log only when true (UTC) time is available.
        "
    ::= { vcaMib 3 }

--
-- vcaIfTable
--

vcaIfTable OBJECT-TYPE
    SYNTAX SEQUENCE OF VcaIfEntry
    MAX-ACCESS    not-accessible
    STATUS        current
    DESCRIPTION
        "A table with a row for each V2X MAC interface in the system."
    ::= { vcaMib 4 }

vcaIfEntry OBJECT-TYPE
    SYNTAX        VcaIfEntry
    MAX-ACCESS    not-accessible
    STATUS        current
    DESCRIPTION
        "VCA management infromation per each V2X MAC interface."
    INDEX         { ifIndex }
    ::= { vcaIfTable 1 }

VcaIfEntry ::=
    SEQUENCE {
        vcaTxPeriod Unsigned32,
        vcaFrameLen Unsigned32,
        vcaTxEnabled TruthValue  }

vcaTxPeriod OBJECT-TYPE
    SYNTAX        Unsigned32 (10..1000)
    UNITS         "milliseconds"
    MAX-ACCESS    read-write
    STATUS        current
    DESCRIPTION
        "Time period between sequential VCA frame transmissions."
    ::= { vcaIfEntry 1 }

vcaFrameLen OBJECT-TYPE
    SYNTAX        Unsigned32 (40..2304)
    UNITS         "octets"
    MAX-ACCESS    read-write
    STATUS        current
    DESCRIPTION
        "Length of IEEE 802.11 MSDU generated by VCA."
    ::= { vcaIfEntry 2 }

vcaTxEnabled OBJECT-TYPE
    SYNTAX        TruthValue
    MAX-ACCESS    read-write
    STATUS        current
    DESCRIPTION
        "Whether VCA frame transmission from this MAC interface is enabled."
    ::= { vcaIfEntry 3 }

vcaConformance OBJECT IDENTIFIER ::= { vcaMib 1 }
vcaGroups      OBJECT IDENTIFIER ::= { vcaConformance 1 }
vcaCompliances OBJECT IDENTIFIER ::= { vcaConformance 2 }

vcaCompliance MODULE-COMPLIANCE
    STATUS current
    DESCRIPTION
        "Compliance statement covering entire AUTOTALKS-VCA-MIB."
    MODULE
           MANDATORY-GROUPS { vcaMibGroup }
    ::= { vcaCompliances 1 }

vcaConfigSaveStatus  OBJECT-TYPE
    SYNTAX        ConfigSaveStatus
    MAX-ACCESS    read-write
    STATUS        current
    DESCRIPTION
        "VCA MIB configuration save status."
    ::= { vcaMib 5 }

vcaMibGroup OBJECT-GROUP
    OBJECTS {
        vcaBsmRxEnabled,
        vcaLogMode,
        vcaTxPeriod,
        vcaFrameLen,
        vcaTxEnabled,
        vcaConfigSaveStatus }
    STATUS current
    DESCRIPTION
        "All objects in AUTOTALKS-VCA-MIB."
    ::= { vcaGroups 1 }

END
